/********************************************************************
 *
 * Copyright (c) IBOA Corp 2016
 *
 * All Rights Reserved
 *                                                                     
 * Redistribution and use in source and binary forms, with or without  
 * modification, are permitted provided that the following conditions 
 * are met:                                                             
 * 1. Redistributions of source code must retain the above copyright    
 *    notice, this list of conditions and the following disclaimer.     
 * 2. Redistributions in binary form must reproduce the above           
 *    copyright notice, this list of conditions and the following       
 *    disclaimer in the documentation and/or other materials provided   
 *    with the distribution.                                            
 *                                                                      
 * THIS SOFTWARE IS PROVIDED BY THE AUTHORS ``AS IS'' AND ANY EXPRESS   
 * OR IMPLIED WARRANTIES, INCLUDING, BUT NOT LIMITED TO, THE IMPLIED    
 * WARRANTIES OF MERCHANTABILITY AND FITNESS FOR A PARTICULAR PURPOSE   
 * ARE DISCLAIMED. IN NO EVENT SHALL THE AUTHORS OR CONTRIBUTORS BE     
 * LIABLE FOR ANY DIRECT, INDIRECT, INCIDENTAL, SPECIAL, EXEMPLARY, OR  
 * CONSEQUENTIAL DAMAGES (INCLUDING, BUT NOT LIMITED TO, PROCUREMENT    
 * OF SUBSTITUTE GOODS OR SERVICES; LOSS OF USE, DATA, OR PROFITS; OR   
 * BUSINESS INTERRUPTION) HOWEVER CAUSED AND ON ANY THEORY OF           
 * LIABILITY, WHETHER IN CONTRACT, STRICT LIABILITY, OR TORT            
 * (INCLUDING NEGLIGENCE OR OTHERWISE) ARISING IN ANY WAY OUT OF THE    
 * USE OF THIS SOFTWARE, EVEN IF ADVISED OF THE POSSIBILITY OF SUCH     
 * DAMAGE.                                                              
 *
 ********************************************************************/
module taga {

    namespace "http://iboa.us/ns/taga";

    prefix "taga";

    organization "IBOA Corp";

    contact "Darrin L. Meek <info@iboa.us>"; 

    description
        "YANG module for IBOA Test Auto Generation and Analysis (TAGA).";

    revision 2016-11-10 {
        description "Initial Version of the TAGA Module.";
    }

    identity taga-type {
        description
          "Base for all taga types.";
    }

    identity taga-type1 {
        description
          "TAGA Type 1.";
        base taga:taga-type;
    }

    identity taga-type2 {
        description
          "TAGA Type 2.";
        base taga:taga-type;
    }

    identity taga-type3 {
        description
          "TAGA Type 3.";
    }

    identity taga-type4 {
        description
          "TAGA Type 4.";
    }


    identity taga-test-type {
        description
          "Base for all taga test types.";
    }

    identity udp-unicast {
        description
          "TAGA Test Type 1 (UDP Unicast).";
        base taga:taga-test-type;
    }

    identity udp-multicast {
        description
          "TAGA Test Type 2 (UDP Multicast).";
        base taga:taga-test-type;
    }

    identity tcp-unicast {
        description
          "TAGA Test Type 3 (TCP Unicast).";
        base taga:taga-test-type;
    }

    identity simulation-only {
        description
          "TAGA Test Type 4 (Simulation Only).  Traffic is not generated";
        base taga:taga-test-type;
    }

    typedef DisplayString {
        description
          "YANG version of the SMIv2 DisplayString TEXTUAL-CONVENTION.";
        reference "RFC 2579, section 2.";
        type string {
            length "0 .. 255";
        }
    }

    container taga {
        presence
          "Indicates the taga service is available";

        description
          "Top-level container for all taga database objects.";

        leaf tagaService {
            type DisplayString;
            config false;
            mandatory true;
            description 
              "The name of the taga service.";
        }
 
        leaf tagaServiceVersionNumber {
            type DisplayString;
            config false;
            mandatory true;
            description
              "The name of the taga service's version.";
        }

        leaf tagaServiceStatus {
            type enumeration {
                enum enabled {
                  value 1;
                  description
                    "The taga service is enabled.";
                }
                enum disabled {
                  value 2;
                  description
                    "The taga service is disabled.";
                }
            }
            config false;
            mandatory true;
            description
              "This variable indicates the current state (enabled or disabled) of the taga service.";
        }
    }

    rpc run-taga {
        description
          "Invoke the taga service.
           The tagaOperational notification is sent when the taga is operational, 
           i.e. after sourcing the taga configuration.  An 'already-running' error is 
           returned if taga is already operational.  A 'resource-denied' error is 
           returned if the taga service is disabled.";
        input {
            leaf tagaLevel {
                type uint32 {
                    range "1 .. 10";
                }
                default 5;
                description
                  "This variable controls the level of taga system interaction. It should
                   be on a scale of 1 to 10 with 1 least interactive (essentially inert).";
            }
            leaf tagaTestType {
                type identityref {
                    base taga:taga-test-type;
                }
                default taga:udp-unicast;
                description
                  "This is the type of test that is being run. 
                   This may impact duration of the test.";
            }
        }
    }

    rpc stop-taga {
        description
          "Stop running taga, if it is running.
           A 'resource-denied' error is returned 
           if the taga service is disabled.";
    }

    notification tagaOperational {
        description
          "Indicates that the taga in operational.";

        leaf tagaStatus {
           description
             "Indicates the current taga status";
           type enumeration {
               enum operational {
                  description
                    "The taga is operational .";
               }
               enum autodisabled {
                  description
                    "The taga was autodisabled.";
               }
               enum cancelled {
                  description
                    "The taga was cancelled.";
               }
               enum error {
                  description
                    "An error occurred during taga processing.";
               }
            }
        }
    }
}
