/********************************************************************
 *
 * Copyright (c) IBOA Corp 2016
 *
 * All Rights Reserved
 *                                                                     
 * Redistribution and use in source and binary forms, with or without  
 * modification, are permitted provided that the following conditions 
 * are met:                                                             
 * 1. Redistributions of source code must retain the above copyright    
 *    notice, this list of conditions and the following disclaimer.     
 * 2. Redistributions in binary form must reproduce the above           
 *    copyright notice, this list of conditions and the following       
 *    disclaimer in the documentation and/or other materials provided   
 *    with the distribution.                                            
 *                                                                      
 * THIS SOFTWARE IS PROVIDED BY THE AUTHORS ``AS IS'' AND ANY EXPRESS   
 * OR IMPLIED WARRANTIES, INCLUDING, BUT NOT LIMITED TO, THE IMPLIED    
 * WARRANTIES OF MERCHANTABILITY AND FITNESS FOR A PARTICULAR PURPOSE   
 * ARE DISCLAIMED. IN NO EVENT SHALL THE AUTHORS OR CONTRIBUTORS BE     
 * LIABLE FOR ANY DIRECT, INDIRECT, INCIDENTAL, SPECIAL, EXEMPLARY, OR  
 * CONSEQUENTIAL DAMAGES (INCLUDING, BUT NOT LIMITED TO, PROCUREMENT    
 * OF SUBSTITUTE GOODS OR SERVICES; LOSS OF USE, DATA, OR PROFITS; OR   
 * BUSINESS INTERRUPTION) HOWEVER CAUSED AND ON ANY THEORY OF           
 * LIABILITY, WHETHER IN CONTRACT, STRICT LIABILITY, OR TORT            
 * (INCLUDING NEGLIGENCE OR OTHERWISE) ARISING IN ANY WAY OUT OF THE    
 * USE OF THIS SOFTWARE, EVEN IF ADVISED OF THE POSSIBILITY OF SUCH     
 * DAMAGE.                                                              
 *
 ********************************************************************/
module tpol {

    namespace "http://iboa.us/ns/tpol";

    prefix "tpol";

    organization "IBOA Corp";

    contact "Darrin L. Meek <info@iboa.us>"; 

    description
        "YANG module for IBOA Test Auto Generation and Analysis (TAGA) Policy Management (POL) (TPOL).";

    revision 2016-11-12 {
        description "Nov 2016 Updates to the Initial Version of the TAGA Policy Management (TPOL) Module.";
    }

    identity tpol-type {
        description
          "Base for all tpol types.";
    }

    identity tpol-type-pol {
        description
          "TPOL Log File Type .";
        base tpol:tpol-type;
    }

    identity tpol-type-dat {
        description
          "TPOL Dat File Type .";
        base tpol:tpol-type;
    }

    identity tpol-type-out {
        description
          "TPOL OUT File Type .";
        base tpol:tpol-type;
    }

    identity tpol-type-txt {
        description
          "TPOL TXT File Type .";
        base tpol:tpol-type;
    }

    identity tpol-type1 {
        description
          "TAGA Type 1.";
        base tpol:tpol-type;
    }

    identity tpol-type2 {
        description
          "TAGA Type 2.";
        base tpol:tpol-type;
    }

    identity tpol-type3 {
        description
          "TAGA Type 3.";
    }

    identity tpol-type4 {
        description
          "TAGA Type 4.";
    }


    identity tpol-test-type {
        description
          "Base for all tpol test types.";
    }

    identity udp-unicast {
        description
          "TAGA Test Type 1 (UDP Unicast).";
        base tpol:tpol-test-type;
    }

    identity udp-multicast {
        description
          "TAGA Test Type 2 (UDP Multicast).";
        base tpol:tpol-test-type;
    }

    identity tcp-unicast {
        description
          "TAGA Test Type 3 (TCP Unicast).";
        base tpol:tpol-test-type;
    }

    identity simulation-only {
        description
          "TAGA Test Type 4 (Simulation Only).  Traffic is not generated";
        base tpol:tpol-test-type;
    }

    typedef DisplayString {
        description
          "YANG version of the SMIv2 DisplayString TEXTUAL-CONVENTION.";
        reference "RFC 2579, section 2.";
        type string {
            length "0 .. 255";
        }
    }

    container tpol {
        presence
          "Indicates the tpol service is available";

        description
          "Top-level container for all tpol database objects.";


        leaf tpolMessageDeliveryMode {
           description
             "Indicates the TPOL Message Delivery mode.";
           type enumeration {
               enum immediate {
                  description
                    "The Messages are immediate.";
               }
               enum expedited {
                  description
                    "The Messages are expedited.";
               }
               enum max-reliable {
                  description
                    "The Messages are sent with maximum reliability.";
               }
               enum network-friendly {
                  description
                    "The Messages are sent in a network friendly manner.";
               }
               enum hybrid {
                  description
                    "The Messages are sent via a hybrid policy.";
               }
            }
        }



        leaf tpolCommandMode {
           description
             "Indicates the TPOL Command mode.";
           type enumeration {
               enum immediate {
                  description
                    "The commands are immediate.";
               }
               enum expedited {
                  description
                    "The commands are expedited.";
               }
               enum max-reliable {
                  description
                    "The commands are sent with maximum reliability.";
               }
               enum network-friendly {
                  description
                    "The commands are sent in a network friendly manner.";
               }
               enum hybrid {
                  description
                    "The commands are sent via a hybrid policy.";
               }
            }
        }



        leaf tpolCommandReplyMode {
           description
             "Indicates the TPOL Command Reply mode.";
           type enumeration {
               enum immediate {
                  description
                    "The command replies are immediate.";
               }
               enum expedited {
                  description
                    "The command replies are expedited.";
               }
               enum max-reliable {
                  description
                    "The command replies are sent with maximum reliability.";
               }
               enum network-friendly {
                  description
                    "The command replies are sent in a network friendly manner.";
               }
               enum hybrid {
                  description
                    "The command replies are sent via a hybrid policy.";
               }
            }
        }




        leaf tpolPurgeMode {
           description
             "Indicates the TPOL purge mode.";
           type enumeration {
               enum time-based {
                  description
                    "The purge mode is based on time.";
               }
               enum size-based {
                  description
                    "The purge mode is based on size.";
               }
               enum space-based {
                  description
                    "The purge mode is based on space.";
               }
               enum hybrid-based {
                  description
                    "The purge mode is based on a hybrid of time, size, and space.";
               }
            }
        }

        leaf tpolServiceEnabled {
           type boolean;
           default false;
           description 
              "Flag indicating whether or not the TlM Service is enabled.";
        }

        leaf maxLogDurationMinutes {
           type uint32 {
           range "1 .. 1000000";
           }
           default 10000;
           description
           "The max duration, in minutes, to maintain pols in the pol archive.";
        }

        leaf maxDuration {
           type uint32 {
           range "1 .. 1000000";
           }
           default 10000;
           description
           "The max duration, in minutes, to maintain pols in the pol archive.";
        }

        leaf tpolService {
            type DisplayString;
            config false;
            mandatory true;
            description 
              "The name of the tpol service.";
        }
 
        leaf tpolServiceVersionNumber {
            type DisplayString;
            config false;
            mandatory true;
            description
              "The name of the tpol service's version.";
        }

        leaf tpolServiceStatus {
            type enumeration {
                enum disabled {
                  value 1;
                  description
                    "The tpol service is disabled.";
                }
                enum enabled-active {
                  value 2;
                  description
                    "The tpol service is enabled and active.";
                }
                enum enabled-inactive {
                  value 3;
                  description
                    "The tpol service is enabled and inactive.";
                }
            }
            config false;
            mandatory true;
            description
              "This variable indicates the current state (enabled or disabled) of the tpol service.";
        }
    }

    rpc run-tpol {
        description
          "Invoke the tpol service.
           The tpolOperational notification is sent when the tpol is operational, 
           i.e. after sourcing the tpol configuration.  An 'already-running' error is 
           returned if tpol is already operational.  A 'resource-denied' error is 
           returned if the tpol service is disabled.";
        input {
            leaf tpolLevel {
                type uint32 {
                    range "1 .. 10";
                }
                default 5;
                description
                  "This variable controls the level of tpol system interaction. It should
                   be on a scale of 1 to 10 with 1 least interactive (essentially inert).";
            }
            leaf tpolTestType {
                type identityref {
                    base tpol:tpol-test-type;
                }
                default tpol:udp-unicast;
                description
                  "This is the type of test that is being run. 
                   This may impact duration of the test.";
            }
        }
    }

    rpc stop-tpol {
        description
          "Stop running tpol, if it is running.
           A 'resource-denied' error is returned 
           if the tpol service is disabled.";
    }

    rpc tpol-enable {
        description
          "Stop running tpol, if it is running.
           A 'resource-denied' error is returned 
           if the tpol service is disabled.";
    }

    rpc tpol-disable {
        description
          "Stop running tpol, if it is running.
           A 'resource-denied' error is returned 
           if the tpol service is disabled.";
    }

    notification tpolOperational {
        description
          "Indicates that the tpol in operational.";


        leaf tpolStatus {
           description
             "Indicates the current tpol status";
           type enumeration {
               enum operational {
                  description
                    "The tpol is operational .";
               }
               enum autodisabled {
                  description
                    "The tpol was autodisabled.";
               }
               enum cancelled {
                  description
                    "The tpol was cancelled.";
               }
               enum error {
                  description
                    "An error occurred during tpol processing.";
               }
            }
        }
    }
}
